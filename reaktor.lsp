(vl-load-com) 
(vl-load-reactors)

(setq acadObj (vlax-get-acad-object))
(setq doc (vla-get-ActiveDocument acadObj))
(setq util (vla-get-Utility doc))
(setq layers (vla-get-Layers doc))
(setq mspace (vla-get-ModelSpace doc))
(setq pspace (vla-get-PaperSpace doc))

(foreach grp (vlr-reactors  :vlr-command-reactor )
	(foreach obj (cdr grp)
		;(setq objreclist (vlr-owners obj))
		(vlr-pers-release obj)
		(vlr-remove obj)
		;(foreach obj1 objreclist
		;		(print obj1)
		;		(vlr-owner-remove obj obj1)
		;)	
	)
)

(foreach grp (vlr-reactors  :vlr-object-reactor )
	(foreach obj (cdr grp)
		(if (= "Label:Reactor" (vlr-data obj))
		(progn
			(setq objreclist (vlr-owners obj))
			(vlr-pers-release obj)
			(vlr-remove obj)
			;(print objreclist)
			;(print (assoc "Free" objreclist))
			(foreach obj1 objreclist
				(if (and
						(equal "AcDbPolyline" (vl-catch-all-apply 'vla-get-objectname (list obj1)))
					)
					(vlr-owner-remove obj obj1)
				)
			)
			(setq objreclist (vlr-owners obj))
			(foreach obj1 objreclist
				(if (and
						(equal "AcDbPolyline" (vl-catch-all-apply 'vla-get-objectname (list obj1)))
					)
					(vlr-owner-remove obj obj1)
				)
			)
			(setq objreclist (vlr-owners obj))
			(foreach obj1 objreclist
				(if (and
						(equal "AcDbPolyline" (vl-catch-all-apply 'vla-get-objectname (list obj1)))
					)
					(vlr-owner-remove obj obj1)
				)
			)
		)
		)
	)
)

(if (null *Label:Reactor* ) 
	(progn
		(setq objreclist (list))
		(vlax-for obj mspace
			(if (and
				(equal "AcDbPolyline" (vla-get-objectname obj))
				;(equal "0projekt" (vla-get-layer obj))	
				;(or
					;(equal "0 proj kabel" (vla-get-layer obj))
					;(equal "0 proj przy" (vla-get-layer obj))	
					;(equal "0 proj rury" (vla-get-layer obj))	
					;(equal "0" (vla-get-layer obj))	
					(equal 0 (vl-string-search "0" (vla-get-layer obj)))
				;)
				(or
					(and
						(equal 5 (LM:get-color obj))
						(equal 0 (vla-get-length obj))					
					)
					(equal 1 (LM:get-color obj))	
				)
				)
			(progn				
				(setq objreclist (cons obj objreclist))
			)
			)
		)
		;(print objreclist)
		(setq *Label:Reactor* (vlr-object-reactor objreclist "Label:Reactor" '((:vlr-modified . Label:Reactor:Update)))) 
		;(vlr-command-reactor nil '((:vlr-commandEnded . Label:Reactor:Xdata)))
		;(vlr-pers *Label:Reactor*)
		(setq objreclist nil)
		(print "Reaktor stworzony")
	)
	(progn 
		(vlax-for obj mspace
			(if (and
				(equal "AcDbPolyline" (vla-get-objectname obj))
				;(or
					;(equal "0 proj kabel" (vla-get-layer obj))	
					;(equal "0 proj przy" (vla-get-layer obj))	
					;(equal "0 proj rury" (vla-get-layer obj))	
					;(equal "0" (vla-get-layer obj))	
					(equal 0 (vl-string-search "0" (vla-get-layer obj)))	
				;)
				(or
					(and
						(or
							(equal 256 (LM:get-color obj))
							(equal 5 (LM:get-color obj))
						)
						(equal 0 (vla-get-length obj))					
					)	
					(equal 1 (LM:get-color obj))	
				)
				)
			(progn				
				(vlr-owner-add *Label:Reactor* obj)
			)
			)
		)
		(print "Dodano do reaktora")
		;(vlr-owner-add *Label:Reactor* objrec)
	)
)

(if (null *Command:Reactor* ) 
	(progn
		;(setq *Command:Reactor* (vlr-command-reactor "Command:Reactor" '((:vlr-commandWillStart . Command:Reactor:Start)(:vlr-commandEnded . Command:Reactor:Ended) ))) 
		;(vlr-command-reactor nil '((:vlr-commandEnded . Label:Reactor:Xdata)))
		;(vlr-pers *Command:Reactor*)
	)
	)
;;----------------------------------------------------------------------;;

(defun LM:label:reactor ( on / acadObj doc util layers mspace pspace)
	(setq acadObj (vlax-get-acad-object))
	(setq doc (vla-get-ActiveDocument acadObj))
	(setq util (vla-get-Utility doc))
	(setq layers (vla-get-Layers doc))
	(setq mspace (vla-get-ModelSpace doc))
	(setq pspace (vla-get-PaperSpace doc))
	
	(defun *error* ( msg / )
		(if (not (null msg ) )         
		(progn 
			(princ "\n Label:Reactor:onoff : *error*: " ) 
			(print msg ) 
			;(print objreclist)
			
		)
		)
	)
	nil
	
)

;;;;;;;;;;;;; BACKUP    ;;;;;;;;;; 
(defun LM:label:reactorBAK ( on / objreclist acadObj doc util layers mspace pspace)
	(setq acadObj (vlax-get-acad-object))
	(setq doc (vla-get-ActiveDocument acadObj))
	(setq util (vla-get-Utility doc))
	(setq layers (vla-get-Layers doc))
	(setq mspace (vla-get-ModelSpace doc))
	(setq pspace (vla-get-PaperSpace doc))
	
	(defun *error* ( msg / )
		;(if (not (null msg ) )         
		;(progn 
			(princ "\n Label:Reactor:onoff : *error*: " ) 
			(print msg ) 
			;(print objreclist)
			
		;)
		;;)
	)
	(setq on t)
	(if on 
	(progn
		;(print objreclist)
		(vlr-add *Label:Reactor*)
		(foreach obj1 objreclist
			;(print obj)
			(if (and
					(equal "AcDbPolyline" (vl-catch-all-apply 'vla-get-objectname (list obj1)))
				)
				(vlr-owner-add *Label:Reactor* obj1)
			)
		)
		(setq objreclist nil)
	)
	(progn 
		(if (equal objreclist nil )
		(progn
			;(print obj )
			(setq objreclist (vlr-owners *Label:Reactor*))
			(foreach obj1 objreclist
				(if (and
						(equal "AcDbPolyline" (vl-catch-all-apply 'vla-get-objectname (list obj1)))
					)
					(vlr-owner-remove *Label:Reactor* obj1)
				)
			)
			(vlr-remove *Label:Reactor*)
		)
		(progn
			
			(print "Error: Object reactor not empty")
			;(vlr-add *Label:Reactor*)
			(foreach obj1 objreclist
				(if (and
						(equal "AcDbPolyline" (vl-catch-all-apply 'vla-get-objectname (list obj1)))
					)
					(vlr-owner-add *Label:Reactor* obj1)
				)
			)
			;(setq objreclist nil)
			(vlr-remove *Label:Reactor*)
			(setq objreclist (vlr-owners *Label:Reactor*))
			(foreach obj1 objreclist
				(if (and
						(equal "AcDbPolyline" (vl-catch-all-apply 'vla-get-objectname (list obj1)))
					)
					(vlr-owner-remove *Label:Reactor* obj1)
				)
			)
		)
		)
	)
	)
	
)

(defun c:recon nil (LM:label:reactor t))
(defun c:recoff nil (LM:label:reactor nil))
(defun c:reclist ( / grp obj obj1 )
	(print (vlr-pers-list))
	(foreach grp (vlr-reactors :vlr-command-reactor :vlr-lisp-reactor :vlr-object-reactor)
		;(print grp)
		(foreach obj (cdr grp)
			(if (= "Label:Reactor" (vlr-data obj))
			(progn
				(print (vlr-data obj))
				(print (vlr-owners obj))
			)
			(progn
				(print (vlr-data obj))
			)
			)
			
		)
	)
)

(defun c:recclean ( / objreclist grp obj obj1 )
	(foreach grp (vlr-reactors :vlr-command-reactor :vlr-lisp-reactor :vlr-object-reactor)
		(foreach obj (cdr grp)
			(if (= "Label:Reactor" (vlr-data obj))
			(progn
				(setq objreclist (vlr-owners obj))
				(vlr-pers-release obj)
				(vlr-remove obj)
				;(print objreclist)
				;(print (assoc "Free" objreclist))
				(foreach obj1 objreclist
					; (vl-catch-all-apply 'vla-get-objectname (list obj1))
					(if (and
							;(not (vl-catch-all-apply 'vlax-erased-p  (list obj1)) ) 
							(equal "AcDbPolyline" (vl-catch-all-apply 'vla-get-objectname (list obj1)))
						)
						;(print obj1)
						(vlr-owner-remove obj obj1)
					)
				)
			)
			)
		)
	)
	
)
(defun Command:Reactor:Start ( objrec cmdlist  / thedata area len  label *error*)
	(defun *error* ( msg / )
		;(if (not (null msg ) )         
		;(progn 
			(princ "\n Command:Reactor:Start  : *error*: " ) 
			(print msg ) 
			
			
		;)
		;;)
	)
	
	;(print "START REC")
	;(print objrec)
	;(print (car cmdlist))
	(if	(or 
			(wcmatch (car cmdlist ) "U")
			(wcmatch (car cmdlist ) "UNDO")
			(wcmatch (car cmdlist ) "MREDO")
		)
	(progn
		(if (not (null *Label:Reactor* )) 
		(progn
			(LM:label:reactor nil )
		)
		)
	)
	)
)

(defun Command:Reactor:Ended ( objrec cmdlist  / thedata area len  label *error*)
	(defun *error* ( msg / )
		;(if (not (null msg ) )         
		;(progn 
			(princ "\n Command:Reactor:Ended  : *error*: " ) 
			(print msg ) 
			
			
		;)
		;;)
	)
	;(print "END")
	(if	(or 
			(wcmatch (car cmdlist ) "U")
			(wcmatch (car cmdlist ) "UNDO")
			(wcmatch (car cmdlist ) "MREDO")
		)
	(progn
		(if (not (null *Label:Reactor* )) 
		(progn
			(LM:label:reactor t)
		)
		)
	)
	)
)

(defun Label:Reactor:Update ( objrec reactor params / acadObj doc util layers mspace pspace kable en i le text objtext thexdata thexdatak thexdatap thexdatar thexdatao objRura1 objRura2 cord cord1 cord2 lenRura1 lenRura2 ro lobj objOpis pos1 pos2 lenRura eobjKabel podmianaText objPunkt eobjrec msg thedata area len  label *error*)
	(defun *error* ( msg / )
		;(if (not (null msg ) )         
		;(progn 
			(princ "\n Label:Reactor:Update : *error*: " ) 
			(print msg ) 
			(print eobjrec) 
			(print objrec)
			(print thexdata)
			(print objtext)
			(print text)
			(print le)
			
		;)
		;;)
	)
	;(cd:SYS_UndoBegin)
	;(print "Test reactor")
	(LM:label:reactor  nil )
	;(setvar "CMDECHO" 0)
	(setq acadObj (vlax-get-acad-object))
	(setq doc (vla-get-ActiveDocument acadObj))
	(setq util (vla-get-Utility doc))
	(setq layers (vla-get-Layers doc))
	(setq mspace (vla-get-ModelSpace doc))
	(setq pspace (vla-get-PaperSpace doc))
	(setq kable (list
			'("YAKXs4x16" "50" "75")
			'("YAKXs5x16" "50" "75")
			'("YAKXs4x25" "50" "75")
			'("YAKXs5x25" "50" "75")
			'("YAKXs4x35" "50" "75")
			'("YAKXs4x50" "50" "75")
			'("YAKXs4x70" "75" "75")
			'("YAKXs4x95" "75" "110")
			'("YAKXs4x120" "75" "110")
			'("YAKXs4x150" "110" "160")
			'("YAKXs4x240" "110" "160")	
	))
	( if (and 
			(not (vlax-erased-p objrec ) ) 
			;(/= (vlax-vla-object->ename objrec))
		 )
	( progn
		(setq eobjrec (vlax-vla-object->ename objrec))
		;(print eobjrec)
		(if (and
				;(equal a 1)
				(/= eobjrec nil)
				(equal 1 (LM:get-color-rec objrec))
				(cd:XDT_GetXData eobjrec nil)
			)
		(progn
			(print "Line rec")

			;(cd:XDT_CheckXData eobjrec "opiskabla")
			;(cd:XDT_CheckXData eobjrec "rura")
			(setq le (vla-get-length objrec))
			(setq thexdata (cd:XDT_GetXData eobjrec "opiskabla"))
			(if (/= thexdata nil)
			(progn
				(if (equal "DASHED" (LM:get-linetype-rec objrec))
					(setq text (strcat "L="(rtos le 2 0) "/" (rtos (+ 4 (* 1.04 le)) 2 0) "m"))
					;(setq text (strcat (rtos le 2 0) "/" (rtos (* 1.04 le) 2 0) "m"))
					(setq text (strcat "L="(rtos le 2 0) "/" (rtos (+ 2 le) 2 0) "m"))
				)
				(setq i 0)
				(while (< (setq i (1+ i)) (length thexdata))
					(setq en (handent (cdr (nth i thexdata))))
					(if (and 
						;(/= thexdata nil)
						(/= en nil)
						)
					(progn
						(setq objtext (vlax-ename->vla-object en))
						(vla-put-TextString objtext text)
					)
					)
				)
				;(setq i (1+ i))
			)
			)
			;(LM:elist eobjrec)
		)
		)
		(if (and
				(equal 5 (LM:get-color objrec))
				(equal 0 (vla-get-length objrec))
				;(equal "" objrec)
			)
		(progn
			(print "Rura rec")
			
			;(setq cord2 (list (nth 3 (reverse cord)) (nth 2 (reverse cord)) ))
			(setq eobjrec (vlax-vla-object->ename objrec))
			(setq thexdatak (cd:XDT_GetXData eobjrec "kabel"))
			(setq thexdatap (cd:XDT_GetXData eobjrec "rurapunkt"))
			(setq thexdatar (cd:XDT_GetXData eobjrec "rura"))
			;(setq thexdatao (cd:XDT_GetXData eobjrec "opisrury"))
			(print "OKEJ1")
			;(print cord1)
			;(print cord2)
			;(print thexdatar)
			;(print thexdatak)
			;(print (vlax-dump-object objrec T))
			
			;(setq thexdatar2 (cd:XDT_GetXData (handent (cdr (nth 1 thexdatar))) "rura"))
			;(setq objRura2 (vlax-ename->vla-object (handent (cdr (nth 1 thexdatar2)))))
			;(print "objRURA")
			;(print objRura2)
			(if (and 
					(/= thexdatar nil)
					(/= thexdatap nil)
					(/= thexdatak nil)
				)
			(progn	
				;(print "OKEJ20")
				;(print thexdatar)
				(setq objRura1 (vlax-ename->vla-object (setq eRura1 (handent (cdr (nth 1 thexdatar))))))
				;(print "OKEJ21")
				(setq objRura2 (vlax-ename->vla-object (handent (cdr (nth 2 thexdatar)))))
				;(print "OKEJ22")
				(setq objPunkt (vlax-ename->vla-object (handent (cdr (nth 1 thexdatap)))))
				;(print "OKEJ23")
				(setq thexdatao (cd:XDT_GetXData eRura1 "opisrury"))
				;(print "OKEJ24")
				(setq eobjKabel (handent (cdr (nth 1 thexdatak))))
				(setq objKabel (vlax-ename->vla-object eobjKabel))
				;(print "OKEJ2")
				(setq cord (vlax-safearray->list (vlax-variant-value (vla-get-coordinates objrec))))
				(setq cord1 (list (nth 0 cord) (nth 1 cord) ))
				(setq cord (vlax-safearray->list (vlax-variant-value (vla-get-coordinates objPunkt))))
				(setq cord2 (list (nth 0 cord) (nth 1 cord) ))
				;(setq newpoint (list (vlax-curve-getClosestPointTo objKabel cord1 ) (vlax-curve-getClosestPointTo objKabel cord2 ) ))
				;(setq newpoint (list (vl-remove 0.0 (car newpoint)) (vl-remove 0.0 (cadr newpoint))))
				(setq newpoint (list cord2 cord1 objKabel))
				;(vla-put-visible objPunkt :vlax-false)
				;(print newpoint)
				(if (equal (setq ro (LM:rur objRura1 objRura2)) "dvr")
					(setq war 50)
					(setq war 30)
				)
				(setq ro (strcase ro))
				(setq lobj (LM:rura newpoint 2 war "Automatyczne"))
				(vlr-owner-remove *Label:Reactor* (nth 3 lobj))
				(vlr-owner-remove *Label:Reactor* (nth 4 lobj))
				;(print "OKEJ3")
				;(setq e1 (vlax-vla-object->ename (car lobj)))
				;(setq e2 (vlax-vla-object->ename (cadr lobj)))
				(setq cord1 (vla-get-Coordinates (car lobj)))
				(setq cord2 (vla-get-Coordinates (cadr lobj)))
				(vla-put-Coordinates objRura1 cord1)
				(vla-put-Coordinates objRura2 cord2)
				
				;(vla-delete objRura2)
				(vla-delete (nth 0 lobj))
				(vla-delete (nth 1 lobj))
				(vla-delete (nth 3 lobj))
				(vla-delete (nth 4 lobj))
				(setq lenRura1 (vla-get-length objRura1))
				(setq lenRura2 (vla-get-length objRura2))
				(if (> lenRura1 lenRura2)
					(setq lenRura lenRura1)
					(setq lenRura lenRura2)
				)
				
				(print (strcat "Długość rury: " (rtos lenRura 2 2) "m"))
				;(setq objPunkt2 (vlax-ename->vla-object (handent (cdr (nth 0 thexdatap)))))
				
				;(setq groupList (kr:GRP_GroupNames objRura1))
				;(print (kr:GRP_GroupNames eR2))
				;(print groupList)
				;(foreach L% groupList
				;	(kr:GRP_DeleteGroupbyName L%)
				;)
				;(LM:GRP (list objRura1 objRura2 objPunkt objPunkt2))
				;(print "OKEJ4")
				(if ;(and 
						(/= thexdatao nil)
						;(/= eobjKabel nil)
					;)
				(progn
					(print "TEST opis rury")
					;(setq thexdatao1 (cd:XDT_GetXData eobjrec "opisrury"))
					;(setq thexdatar (cd:XDT_GetXData eobjKabel "rodzaj"))
					(setq i 0)
					
					(while (< (setq i (1+ i)) (length thexdatao))
						(setq objOpis (vlax-ename->vla-object (handent (cdr (nth i thexdatao)))))
						;(print objOpis)
							(if (not (vlax-erased-p objOpis ) )
							(progn					
								(setq textObjOpis (vla-get-TextString objOpis))
								(setq pos1 (vl-string-search "L-" textObjOpis))
								(setq pos2 (vl-string-search "m" textObjOpis pos1))
								(setq pos1 (+ 1 pos1))
								(setq pos2 (+ 2 pos2))
								;(print pos1)
								;(print pos2)
								(setq podmianaText (substr textObjOpis pos1 (- pos2 pos1 )))
								(vla-put-TextString objOpis (vl-string-subst (strcat "L-"(rtos lenRura 2 0) "m" ) podmianaText textObjOpis))	
								
								; (vla-put-TextString objOpis (strcat "proj. rura osłonowa " ro 
									; (if (and
											; ;(equal thexdatar nil)
											; (equal ro "SRS") 
										; )
										; (nth 1 (assoc (cdr (nth 1 thexdatar)) kable)) 
										; (nth 2 (assoc (cdr (nth 1 thexdatar)) kable))
									; )
									; " " "\n" "L-"(rtos lenRura 2 0) "m" )
								; )
							)
							)
					)
				)
				)
			)
			)
		)
		)
	)
	)
	
	(LM:label:reactor t )
	;(setvar "CMDECHO" 1)
	;(cd:SYS_UndoEnd)
)
