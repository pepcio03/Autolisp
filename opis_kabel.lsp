(defun c:opiskabla (/ layer test p c w h p1 p2 p3 p4 ss vp layers pspace mspace util doc acadObj textObj) 
	(cd:SYS_UndoBegin)
	(if (not (null *Label:Reactor* )) 
	(progn
		(LM:label:reactor nil )
	)
	)
	(setvar "CMDECHO" 0)
	(setq layer (getvar "clayer"))
	
	(setq acadObj (vlax-get-acad-object))
    (setq doc (vla-get-ActiveDocument acadObj))
	(setq util (vla-get-Utility doc))
	(setq layers (vla-get-Layers doc))
	(setq mspace (vla-get-ModelSpace doc))
	(setq pspace (vla-get-PaperSpace doc))
	
	(defun *error* ( msg )
        (print msg)
		;(if (wcmatch msg "ObjectIdToObject")
		(princ "\n*error* program opis_kabel .")
			
        ;)
		
    )
	
	
	(setq vp nil)
	(setq objKabel nil)
	(setq test nil) 
	(print (strcat "Aktualna warstwa : " layer))
	
	(defun _move ( ent p / ss )
		( setq ss (ssadd ))
		( ssadd  ( vlax-vla-object->ename ent ) ss )
		(command "_MOVE" ss "" p pause )
	)
	(defun _rotate ( ent / ss p )
		( setq ss (ssadd ))
		( ssadd  ( vlax-vla-object->ename ent ) ss )
		(setq p (vlax-safearray->list (vlax-variant-value (vla-get-InsertionPoint ent))))
		(command "_ROTATE" ss "" p pause )
	)
	
	(setq p (getpoint "Wska¿ punkt na kablu:"))
	
	(vlax-for obj pspace 
	;(setq obj (vlax-ename->vla-object (car (entsel))))
	;(print (vla-get-objectname obj))
		(if (and
			(equal (vla-get-objectname obj) "AcDbViewport")
			;(equal vp nil)
			)
		(progn
			(setq c (vlax-safearray->list (vlax-variant-value (vla-get-center obj))))
			(setq w (/ (vla-get-Width obj) 2))
			(setq h (/ (vla-get-Height obj) 2))
			(setq   p1 (- (car c) w)
					p2 (+ (cadr c) h)
					p3 (+ (car c) w)
					p4 (- (cadr c) h)
			)
			
			;(print obj)
			;(print c)
			;(print w)
			;(print h)
			
			(if (and
					;(> p1 0)
					;(> p2 0)
					;(> p3 0)
					;(> p4 0)
					(> (car p) p1)
					(< (cadr p) p2)
					(< (car p) p3)
					(> (cadr p) p4)
				)
			(progn
				(setq vp obj)
			)			
			)
		)
		)
	)
	
	(setq pt (PCS2WCS p vp))
	(setq objPt (vlax-3D-point pt))
	(setq radius 0.25)
	(print p)
	(print pt)
	(setq thepoint (vla-AddCircle mspace objPt radius))
	
	(vlax-for obj mspace
		(if (and
				(equal "AcDbPolyline" (vla-get-objectname obj))
				(equal layer (vla-get-layer obj))	
				(/= 5 (LM:get-color obj))	
			)
			(progn				
				(if (equal test nil)
				(progn
					(setq objKabel obj)
					(setq intPoints (vla-IntersectWith thepoint objKabel acExtendNone))	
					(setq test (vlax-safearray->list (vlax-variant-value intPoints)))
					;(print objKabel)
				)
				)
			)
			)
	)
	
	(vla-delete thepoint)
	(print test)
	(if test 
	(progn
		(setq l (vla-get-length objKabel))
		(if (equal "DASHED" (LM:get-linetype objKabel))
			(setq textObj (vla-AddMText pspace (vlax-3D-point p) 10 (strcat "L="(rtos l 2 0) "/" (rtos (+ 4 (* 1.04 l)) 2 0) "m")))
			(setq textObj (vla-AddMText pspace (vlax-3D-point p) 10 (strcat "L="(rtos l 2 0) "/" (rtos (+ 2 l) 2 0) "m")))
			;(setq textObj (vla-AddMText pspace (vlax-3D-point p) 10 (strcat (rtos l 2 0) "/" (rtos (* 1.04 l) 2 0) "m")))
		)
		(vla-put-height textObj 2.5)
		(vla-put-color textObj 7)
		(vla-put-StyleName textObj "Arial")
		(setq eText (vlax-vla-object->ename textObj))
		(setq eKabel (vlax-vla-object->ename objKabel))
		(cd:XDT_CheckXData eKabel "opiskabla")
		(mask:maskentity eText t 1.5 nil '((62 . 31)))
		(entmod eText)
		(_move textObj p)
		(_rotate textObj)
		;(setq DataType (vlax-make-safearray vlax-vbInteger '(0 . 3)))
		;(setq Data (vlax-make-safearray vlax-vbVariant '(0 . 3)))
		;(vlax-safearray-put-element DataType 0 1001)
		;(vlax-safearray-put-element Data 0 "opiskabla")
		;(vlax-safearray-put-element DataType 1 1002)
		;(vlax-safearray-put-element Data 1 "{")
		;(vlax-safearray-put-element DataType 2 1005)
		;(vlax-safearray-put-element Data 2 (vla-get-Handle textObj))
		;(vlax-safearray-put-element DataType 3 1002)
		;(vlax-safearray-put-element Data 3 "}")
		;(vl-cmdf "_mspace" "")
		;(vla-SetXData objKabel DataType Data)
		;(vl-cmdf "_pspace" "")
		;(progn
		(cd:XDT_UpdateXData eKabel "opiskabla" (list (vla-get-Handle textObj)))
		(cd:XDT_UpdateXData eText "kabel" (list (vla-get-Handle objKabel)))
		;)
		;(cd:XDT_UpdateXData eText "kabel" (list (vlax-vla-object objKabel)))
		(princ)
	)
	)
	(setvar "CMDECHO" 1)
	(if (not (null *Label:Reactor* )) 
	(progn
		(LM:label:reactor t )
	)
	)
	(cd:SYS_UndoEnd)
)

(defun c:opiskabelauto ( / i list_dz acadObj doc util layers mspace pspace list_dz_sort list_dz_all )
	(cd:SYS_UndoBegin)
	;(setvar "cmdecho" 0)
	(setq acadObj (vlax-get-acad-object))
	(setq doc (vla-get-ActiveDocument acadObj))
	(setq util (vla-get-Utility doc))
	(setq layers (vla-get-Layers doc))
	(setq mspace (vla-get-ModelSpace doc))
	(setq pspace (vla-get-PaperSpace doc))
	
	(setq layer (getvar "clayer"))
	(setq list_dz (list))
	(setq i 0)

	(setq vp nil)
	(setq objKabel nil)
	(setq test nil)
	(print (strcat "Aktualna warstwa : " layer))
	(setq gora (/ pi 2))
	(setq dol (/ (* pi 3) 2))
	(setq lewo pi )
	(setq prawo 0)
	(defun _move ( ent p / ss )
		( setq ss (ssadd ))
		( ssadd  ( vlax-vla-object->ename ent ) ss )
		(command "_MOVE" ss "" p pause )
	)
	(defun _rotate ( ent / ss p )
		( setq ss (ssadd ))
		( ssadd  ( vlax-vla-object->ename ent ) ss )
		(setq p (vlax-safearray->list (vlax-variant-value (vla-get-InsertionPoint ent))))
		(command "_ROTATE" ss "" p pause )
	)
	
	(setq p (getpoint "Kliknij w rzutnie"))
	(vlax-for obj pspace 
		(if (and
			(equal (vla-get-objectname obj) "AcDbViewport")
			;(equal vp nil)
			)
		(progn
			(setq c (vlax-safearray->list (vlax-variant-value (vla-get-center obj))))
			(setq w (/ (vla-get-Width obj) 2))
			(setq h (/ (vla-get-Height obj) 2))
			(setq   p1 (- (car c) w)
					p2 (+ (cadr c) h)
					p3 (+ (car c) w)
					p4 (- (cadr c) h)
			)
			(if (and
					(> (car p) p1)
					(< (cadr p) p2)
					(< (car p) p3)
					(> (cadr p) p4)
				)
			(progn
				(setq vp obj)
				(setq c (vlax-safearray->list (vlax-variant-value (vla-get-center obj))))
				(setq w (/ (vla-get-Width obj) 2))
				(setq h (/ (vla-get-Height obj) 2))
				(setq   p1 (- (car c) w)
						p2 (+ (cadr c) h)
						p3 (+ (car c) w)
						p4 (- (cadr c) h)
				)
				(setq p1p2 (list p1 p2))
				(setq p3p4 (list p3 p4))
				(print p1p2)
				(print p3p4)
			)			
			)
		)
		)
	)
	
	(print "Test")
	(vlax-for obj mspace
		;(print (vla-get-objectname obj))
		
		(if (and
				(equal "AcDbPolyline" (vla-get-objectname obj))
				(or
					(equal "0 proj kabel" (vla-get-layer obj))
					(equal layer (vla-get-layer obj))
				)
				(/= (vla-get-length obj) 0)
				(or
					(equal 256 (vla-get-color obj))
					(equal 1 (vla-get-color obj))
				)
			)
			(progn
				
				(setq prf (WCS2PCS (vlax-curve-getstartpoint obj) vp)
					  pre (WCS2PCS (vlax-curve-getendpoint obj) vp)
				)
				;(print prf)
				;(print pre)
				(if
					(or
						(and
							(> (car prf) (car p1p2))
							(< (cadr prf) (cadr p1p2))
							(< (car prf) (car p3p4))
							(> (cadr prf) (cadr p3p4))
						)
						(and
							(> (car pre) (car p1p2))
							(< (cadr pre) (cadr p1p2))
							(< (car pre) (car p3p4))
							(> (cadr pre) (cadr p3p4))
						)
					)
				(progn
					(setq list_dz (cons obj list_dz))
					;(print obj)
					(setq i (1+ i))
				)		
				)
			)
		)
	)
	
	(print list_dz)
	(print i)
	(print "test While")
	(setq j -1)
	(while (< (setq j (1+ j)) i)
		;(print "OK")
		(setq obj1 (nth j list_dz))
		(setq pr1 (WCS2PCS (vlax-curve-getstartpoint obj1) vp))
		(setq pr2 (WCS2PCS (vlax-curve-getendpoint obj1) vp))
		
		(if (< (car pr1) (car pr2))
			(setq pr1 pr1 pr2 pr2)
			(setq prt pr1 pr1 pr2 pr2 prt)
		)
		(print pr1)
		(print pr2)
		(setq le1 (cd:Round (vla-get-length obj1) 1))
		
		(setq ang (angle pr1 pr2))
		(setq dis (distance pr1 pr2))
		(setq pr (polar pr1 ang (/ dis 2)))
		(setq pr (polar pr dol 2))
		(setq textObj (vla-AddMText pspace (vlax-3D-point pr) 7 (strcat "L=" (rtos le1 2 0) "/" (rtos (+ 4 (* 1.04 le1)) 2 0) "m")))
		(vla-put-height textObj 2)
		(vla-put-Width textObj 13)
		(vla-put-Color textObj 7)
		(vla-put-Rotation textObj ang)
		(vla-put-AttachmentPoint textObj 2)
		(vla-put-InsertionPoint textObj (vlax-3D-point pr))
		(vla-put-StyleName textObj "Arial")
		(setq eText (vlax-vla-object->ename textObj))
		;(setq eKabel (vlax-vla-object->ename objKabel))
		;(cd:XDT_CheckXData eKabel "opiskabla")
		(mask:maskentity eText t 1.2 nil '((62 . 31)))
		(entmod eText)
		
		(princ)
		;(setq j (1+ j))
	)
	
	(cd:SYS_UndoEnd)
)
