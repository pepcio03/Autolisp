(vl-load-com)

(defun c:odleglosci (/ objlayer points test textObj pt1 pt)
	
	(setq acadObj (vlax-get-acad-object))
    (setq doc (vla-get-ActiveDocument acadObj))
    (setq mspace (vla-get-ModelSpace doc))  
    (setq layers (vla-get-ModelSpace doc))  
	
	(print (LM:LayerSet "0 proj slupy" acRed "CONTINUOUS" acLnWt030))
	(setq objlayer (vla-get-activeLayer doc))

	(print (LM:LayerSet "0 proj kabel" acRed "DASHED" acLnWt030))
	(setq objlayerKabel (vla-get-activeLayer doc))

	(vla-put-activeLayer doc objlayer)
	
	(defun *error* (errmsg)
    ;(if (not (wcmatch errmsg "Function cancelled,quit / exit abort,console break"))
		;(setvar "OSMODE" lastOSMODE)
		;(setvar "clayer" oldlayer)
		;(vla-delete poly)
		(print errmsg)
		;(print "er")
		;(vla-delete textObj)
		(cd:SYS_UndoEnd)
		(setvar "CMDECHO" 1)
		nil
	;)
	); end *error*
	(defun _move ( ent p / ss )
		( setq ss (ssadd ))
		( ssadd  ( vlax-vla-object->ename ent ) ss )
		(command "_MOVE" ss "" p pause )
	)
	(defun _rotate ( ent / ss p )
		( setq ss (ssadd ))
		( ssadd  ( vlax-vla-object->ename ent ) ss )
		(setq p (vlax-safearray->list (vlax-variant-value (vla-get-InsertionPoint ent))))
		(command "_ROTATE" ss "" p pause )
	)
	(cd:SYS_UndoBegin)
	; converts radians to degrees
	(defun RtD (r) (* 180.0 (/ r pi)))
	; converts degrees to radians
	(defun DtR (d) (* pi (/ d 180.0)))
	
	(setq acadObj (vlax-get-acad-object))
    (setq doc (vla-get-ActiveDocument acadObj))
    (setq modelSpace (vla-get-ModelSpace doc))
	(setq i 1 )
	(defun LM:pol (pt1 pt2 / points ptl ptl polyl)
		(setq points (vlax-make-safearray vlax-vbDouble '(0 . 5)))
		(setq ptl (apply 'append (cons pt1 (list pt2))))
		(vlax-safearray-fill points ptl)
		(setq polyl (vla-AddPolyline modelSpace points))
		polyl
	)
	;(setq pss (vlax-make-safearray vlax-vbDouble '(0 . 719)))
	;(setq dist 1.52)
	(setq ptm (cadr (grread t 15 0)))
	
	
	;(setq poly (vla-AddCircle modelSpace (vlax-3d-point 0 0 0) dist))
	;(vla-put-Visible poly :vlax-false)
	(setq dis 0)
	(setq disa -1)
	(setq disw -1)
	(setq disk -1)
	(setq dise -1)
	(setq dist -1)
	(setq diso -1)
	(setq disj -1)
	(setq disg -1)
	(setq el_obiekt (list))
	(setq test nil)
	(vlax-for obj mspace
		(if (or
				;(equal "AcDbPolyline" (vla-get-objectname obj))
				;(equal "0projekt" (vla-get-layer obj))	
				(equal "przewód wodociągowy (linia)" (vla-get-layer obj))	
				(equal "przewód kanalizacyjny (linia)" (vla-get-layer obj))	
				(equal "przewód elektroenergetyczny (linia)" (vla-get-layer obj))	
				(equal "przewód telekomunikacyjny (linia)" (vla-get-layer obj))	
				(equal "przewód gazowy (linia)" (vla-get-layer obj))	
				(equal "jezdnia (powierzchnia)" (vla-get-layer obj))	
				(equal "oprawa" (LM:effectivename obj))
				(equal "zapas" (LM:effectivename obj))
				;(equal "0 proj kabel" (vla-get-layer obj))	
				;(equal 5 (vla-get-color obj))	
			)
			(progn				
					;(setq objKabel obj)
					;(setq intPoints (vla-IntersectWith thepoint objKabel acExtendNone))	
					;(setq test (vlax-safearray->list (vlax-variant-value intPoints)))
					(setq el_obiekt (append el_obiekt (list obj)))
			)
			)
	)
	
	(defun LM:testdis (str tdis dis)
		(if (equal str (vla-get-layer obj))
		(progn
			(if (or
				(= tdis -1)
				(> tdis dis)
				)
			(setq tdis dis test nil)
			)
		)
		)
		tdis
	)
	
	(while i
		(setq pt (grread t 15 0))
		;(print  pt )
		(if (equal  5 (car pt))
		(progn
			(setq ptm (cadr pt))
			;( if (and 
			;	(not (vlax-erased-p textObj ) ) 
				;(/= (vlax-vla-object->ename objrec))
			;)
			;( progn
			;	(vla-delete textObj)
			;)
			;)
			;(print ptm)
			;(vla-put-Center poly (vlax-3d-point ptm))
			;(vla-Update poly)
			;(print "OK")
			;(print (list (car ptm) (cadr ptm)))
			(setq j 0)
			(setq disa -1)
			(setq disw -1)
			(setq disk -1)
			(setq dise -1)
			(setq dist -1)
			(setq disj -1)
			(setq disotemp (list))
			(setq diso (list))
			(setq disg -1)
			(setq test 0)
			(setq disoptm (list))
			(foreach obj el_obiekt 
				;(print "OK1")
				(if (or 
						(equal "zapas" (LM:effectivename obj))
						(equal "oprawa" (LM:effectivename obj))
					)
					(setq p (vlax-safearray->list ( vlax-variant-value ( vla-get-InsertionPoint obj) ) ) )
					(setq p (vlax-curve-getClosestPointTo obj ptm))
				)
				;(print "OK3")
				(setq dis (distance ptm p))
				(setq test (distance ptm p))
				
				(if (< test 10)
				(progn
					;(setq pt ptm)
					;(setq intPoints (vla-IntersectWith poly obj acExtendNone))
					;(setq test (vlax-safearray->list (vlax-variant-value intPoints)))
					;(setq test (vlax-safearray->list (vlax-variant-value (vla-IntersectWith polyl obj acExtendNone))))
					;(print "OK2")
					
					;(vla-delete polyl)
					(setq disw (LM:testdis "przewód wodociągowy (linia)" disw dis))
					(setq disk (LM:testdis "przewód kanalizacyjny (linia)" disk dis))
					(setq dise (LM:testdis "przewód elektroenergetyczny (linia)" dise dis))
					(setq disg (LM:testdis "przewód gazowy (linia)" disg dis))
					(setq dist (LM:testdis "przewód telekomunikacyjny (linia)" dist dis))
					(setq disj (LM:testdis  "jezdnia (powierzchnia)" disj dis))	
				)
				)
				(if (< test 80)
				(progn	
					(if (or 
							(equal "zapas" (LM:effectivename obj))
							(equal "oprawa" (LM:effectivename obj))
						)
					(progn
						;(print dis)
						
						(setq disotemp (cons dis disotemp))
					)
					)
				)
				)
			)
			(setq j 0)
			(setq diso (list))
			(setq disoptm (list))
			(setq distemp nil)
			(while (< j  3)
				(setq distemp (apply 'min disotemp))
				(setq disotemp (vl-remove distemp disotemp ))
				(setq diso (cons distemp diso))
				
				;(setq disoptm (cons disoptm diso))
				
				(setq j (1+ j))
			)
			(setq diso (reverse diso))
			(setq Sdisw (strcat (if (/= disw -1) (strcat "Wóda: " (rtos disw 2 2)) (setq disw ""))))
			(setq Sdisk (strcat (if (/= disk -1) (strcat "  Gówno: " (rtos disk 2 2)) (setq disk ""))))
			(setq Sdise (strcat (if (/= dise -1) (strcat "  Pr1dy: " (rtos dise 2 2)) (setq dise ""))))
			(setq Sdisg (strcat (if (/= disg -1) (strcat "  Gazy: " (rtos disg 2 2)) (setq disg ""))))
			(setq Sdist (strcat (if (/= dist -1) (strcat "  Tele: " (rtos dist 2 2)) (setq dist ""))))
			(setq Sdisj (strcat (if (/= disj -1) (strcat "  Jezdnia: " (rtos disj 2 2)) (setq disj ""))))	
			(setq Sdiso (strcat (if (or (/= (nth 0 diso) 0)(/= (nth 1 diso) 0)(/= (nth 2 diso) 0)) (strcat "  Oprawa/Z: " (rtos (nth 0 diso) 2 2) "|" (rtos (nth 1 diso) 2 2) "|" (rtos (nth 2 diso) 2 2)) (setq diso "  Za daleko"))))
			
			(setq disa (strcat Sdisw Sdisk Sdise Sdist Sdisg Sdisj Sdiso))
			;(setq disa (strcat "Wóda: " (rtos disw 2 2) " Gówno: " (rtos disk 2 2) " Pr1dy: " (rtos dise 2 2) " Tele: " (rtos dist 2 2) " Gazy: " (rtos disg 2 2) " Jezdnia: " (	rtos disj 2 2) " Oprawa/Z: " (rtos (nth 0 diso) 2 2) "|" (rtos (nth 1 diso) 2 2) "|" (rtos (nth 2 diso) 2 2)))
			;(setq disa1 (strcat "W " (rtos disw 2 1) " G " (rtos disk 2 1) " P " (rtos dise 2 1) " T " (rtos dist 2 1) " G " (rtos disg 2 1) " J " (rtos disj 2 1)))
			;(vla-delete poly)
			;(if (or (> dis (distance ptm test))(equal dis 0))
			;	(setq dis (distance ptm test))
			;)
			;(setq insertionPoint (vlax-3d-point ptm))
			;(setq textObj (vla-AddText mspace disa insertionPoint 0.2)) 
			
			(print disa)
			
			;(print dis)
			;(print (distance ptm test))
			;(setq j (+ j 10))
			;)

			;(setq i (1+ i ))
		)
		)
		(if (equal  25 (car pt))
		(progn
			(setq pt (cadr pt))
			(setq obj (cd:BLK_InsertBlock pt "oprawa" '(1 1 1) pi nil))
			(_rotate obj)
			(setq el_obiekt (append el_obiekt (list obj)))
		)
		)
		
		(if (equal  3 (car pt))
		(progn
			(setq pt (cadr pt))
			(setq obj (cd:BLK_InsertBlock pt "oprawa" '(1 1 1) pi nil))
			(_rotate obj)
			(setq el_obiekt (append el_obiekt (list obj)))
			(if pt1 
			(progn
				(setq objlayer (vla-get-activeLayer doc))
				(vla-put-activeLayer doc objlayerKabel)
				(cd:ACX_AddLWPolyline (cd:ACX_ASpace) (list pt1 pt) nil)
				(vla-put-activeLayer doc objlayer)
			)
			)
			(setq pt1 pt)
		)
		)
	)
	;(vla-delete poly)
	(cd:SYS_UndoEnd)
)

(defun c:azorszukaj ( / acadObj doc mspace layer  kLine objLine ssLine dT sP sE dP dE delta dist nDP nP pk ang r90 angplus angminus polar1 polar2 test testObjList intPoints )
	(cd:SYS_UndoBegin)
	(setq acadObj (vlax-get-acad-object))
    (setq doc (vla-get-ActiveDocument acadObj))
    (setq mspace (vla-get-ModelSpace doc))  
	
	(defun *error* (errmsg)
    ;(if (not (wcmatch errmsg "Function cancelled,quit / exit abort,console break"))
		
		(print errmsg)	
		(vla-delete kLine)
		(print objLine)	
		(print sP)
		(print sE)
		(print dP)
		(print dE)
		(print delta)
		(print dist)
		(print nDP)
		(print nP)
		(print intPoints)
		(print pk)
		(print (vla-get-layer obj1))
		
		(cd:SYS_UndoEnd)
		nil
	); end *error*
	(print "OKEJ")
	(setq layer (getvar "clayer"))
	(sssetfirst nil nil )
	(setq ssLine (ssget ":S"
	    (list
			(cons -4 "<AND")
				(cons -4 "<OR")
					(cons 0 "LWPOLYLINE")
					(cons 0 "POLYLINE")
				(cons -4 "OR>")
				(cons -4 "<OR")
					(cons 8 layer)
					(cons 8 "0*")
				(cons -4 "OR>")
				(cons -4 "<NOT")
					;(cons -4 "<AND")
						(cons 62 5)				
					;(cons -4 "<AND")
				(cons -4 "NOT>")
			(cons -4 "AND>")
		)
		)
	)
	(setq objLine (car (cd:SSX_Convert ssLine 1) ))
	
	(setq sP (vlax-curve-getStartPoint objLine))
	(setq sE (vlax-curve-getEndPoint objLine))
	
	(setq dP (vlax-curve-getDistAtPoint objLine sP))
	(setq dE (vlax-curve-getDistAtPoint objLine sE))
	;(print dP)
	;(print dE)
	(setq delta 0.1)
	(setq dist 1)
	
	(if (> dP dE)
		(setq dT dP dE dP dP dT dT sP sE sP sP dT )
	)
	;(setq nDP (+ dP delta))
	(setq i -1)
	(while (and
			(< (setq i (1+ i)) (fix (/ dE delta)))
			(< (+ dP delta) dE)
		    )
		;(setq test T)
		(if (equal nil ok)
			(setq delta 2)
		)
		(setq nDP (+ dP delta))
		(setq nP (vlax-curve-getPointAtDist objLine nDP))
		(setq ang (angle sP nP))
		(setq r90 (LM:DtR 90))
		(setq angplus (+ ang r90))
		(setq angminus (- ang r90))
		
		(setq polar1 (polar nP angplus dist))
		(setq polar2 (polar nP angminus dist))
		
		(setq test (ssget "_F" (list polar1 polar2) ))
		(setq testObjList (cd:SSX_Convert test 1) )
		
		(setq delta 0.1)
		(setq ok T)
		(foreach obj testObjList
			
			(if (and
				(or
					(equal "przewód wodociągowy (linia)" (vla-get-layer obj))	
					(equal "przewód kanalizacyjny (linia)" (vla-get-layer obj))	
					;(equal "przewód elektroenergetyczny (linia)" (vla-get-layer obj))	
					(equal "przewód telekomunikacyjny (linia)" (vla-get-layer obj))	
					(equal "przewód gazowy (linia)" (vla-get-layer obj))
					(equal "jezdnia (powierzchnia)" (vla-get-layer obj))
					(equal "chodnik (powierzchnia)" (vla-get-layer obj))
				)
				ok
				)
			(progn
				
				(setq test2 nil)
				(setq p1 (vlax-curve-getClosestPointTo obj polar1))
				(setq p2 (vlax-curve-getClosestPointTo obj polar2))
				(setq tempLine (cd:ACX_AddLWPolyline (cd:ACX_ASpace) (list p1 p2) nil))
				(setq intPoints (vla-IntersectWith objLine tempLine acExtendNone))
				(setq test2 (vlax-safearray->list (vlax-variant-value intPoints)))
				(vla-delete tempLine)
				(setq jest nil)

				(if (equal nil test2)
				(progn
					;(setq delta 2)
					(setq kLine (cd:ACX_AddLWPolyline (cd:ACX_ASpace) (list polar1 polar2) nil))
					(setq ok nil)
					(setq zcenter (vlax-3d-point nP )
						magnification 10)
					(vla-ZoomCenter acadObj zcenter magnification)
					(princ "\n")
					
					(foreach obj1 testObjList
						
						(cond  
							((equal "przewód wodociągowy (linia)" (vla-get-layer obj1))
								(setq intPoints (vla-IntersectWith kLine obj1 acExtendNone))
								(setq pk (vlax-safearray->list (vlax-variant-value intPoints)))
								(if pk (progn
									(setq pk (list (car pk) (cadr pk) 0.0))
									(setq dis (distance pk nP))
									(if (<= dis 0.7)
									(progn
										(setq jest t)
										(princ (strcat "  Woda:" (rtos dis 2 2)))
									)
									)
								))
								;(princ strcat("  Woda:" dis))
							)							
							((equal "przewód kanalizacyjny (linia)" (vla-get-layer obj1))	
								(setq intPoints (vla-IntersectWith kLine obj1 acExtendNone))
								(setq pk (vlax-safearray->list (vlax-variant-value intPoints)))
								(if pk (progn 
									(setq pk (list (car pk) (cadr pk) 0.0))
									(setq dis (distance pk nP))
									(if (<= dis 0.7)
									(progn
										(setq jest t)
										(princ (strcat "  Kanaliza:" (rtos dis 2 2)))
									)
									)
								))
							)
							;((equal "przewód elektroenergetyczny (linia)" (vla-get-layer obj))	
								;(setq intPoints (vla-IntersectWith kLine obj1 acExtendNone))
								;(setq pk (vlax-safearray->list (vlax-variant-value intPoints)))
								;(if pk (progn
								;	(setq pk (list (car pk) (cadr pk) 0.0))
								;	(setq dis (distance pk nP))
								;	(if (<= dis 0.7)
								;	(progn
								;		(setq jest t)
								;		(princ (strcat "  Telee:" (rtos dis 2 2)))
								;	)
								;	)
								;))
							;)
							((equal "przewód telekomunikacyjny (linia)" (vla-get-layer obj1))	
								(setq intPoints (vla-IntersectWith kLine obj1 acExtendNone))
								(setq pk (vlax-safearray->list (vlax-variant-value intPoints)))
								(if pk (progn
									(setq pk (list (car pk) (cadr pk) 0.0))
									(setq dis (distance pk nP))
									(if (<= dis 0.7)
									(progn
										(setq jest t)
										(princ (strcat "  Tele:" (rtos dis 2 2)))
									)
									)
								))
							)
							((equal "przewód gazowy (linia)" (vla-get-layer obj1))
								(setq intPoints (vla-IntersectWith kLine obj1 acExtendNone))
								(setq pk (vlax-safearray->list (vlax-variant-value intPoints)))
								(if pk (progn
									(setq pk (list (car pk) (cadr pk) 0.0))
									(setq dis (distance pk nP))
									(if (<= dis 1.0)
									(progn
										(setq jest t)
										(princ (strcat "  Gazy:" (rtos dis 2 2)))
									)
									)
								))
							)
							((equal "jezdnia (powierzchnia)" (vla-get-layer obj1))
								(setq intPoints (vla-IntersectWith kLine obj1 acExtendNone))
								(setq pk (vlax-safearray->list (vlax-variant-value intPoints)))
								(if pk (progn
									(setq pk (list (car pk) (cadr pk) 0.0))
									(setq dis (distance pk nP))
									(if (<= dis 0.5)
									(progn
										(setq jest t)
										(princ (strcat "  Jezdnia:" (rtos dis 2 2)))
									))
								))
							)
							((equal "chodnik (powierzchnia)" (vla-get-layer obj1))
								(setq intPoints (vla-IntersectWith kLine obj1 acExtendNone))
								(setq pk (vlax-safearray->list (vlax-variant-value intPoints)))
								(if pk (progn
									(setq pk (list (car pk) (cadr pk) 0.0))
									(setq dis (distance pk nP))
									(if (<= dis 0.5)
									(progn
										(setq jest t)
										(princ (strcat "  Chodnik:" (rtos dis 2 2)))
									)
									)
								))
							)
						)
					)
					
					(if jest
					(progn
						(while  (and
									(/= (car (setq pt (grread t 15 0))) 25 )
									(/= (car pt) 3 )
								)
						)
						(if (equal  25 (car pt))
						(progn
							(vla-delete kLine)
						)
						)
						
						(if (equal  3 (car pt))
						(progn
							;(setq pt (cadr pt))
							;(setq obj (cd:BLK_InsertBlock pt "oprawa" '(1 1 1) pi nil))
							;(_rotate obj)
							;(setq el_obiekt (append el_obiekt (list obj)))
						)
						)
					)
					(progn
						(vla-delete kLine)
						(setq jest nil)
					)
					)
				)
				)
			)
			(progn
				;(setq delta 0.1)
			)
			)
		)
		(setq sP nP dP nDP)
	)
	(princ)
	(cd:SYS_UndoEnd)
)
